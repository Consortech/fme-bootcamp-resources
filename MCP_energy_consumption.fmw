FME workspace MCP_energy_consumption.fmw

Parameters:
- POSTAL_CODE = M9V   # Enter Postal Code
- YEAR = 2024   # Enter desired year
- LIMIT = 30   # Enter query limit
- DestDataset_MCP =   # Destination MCP Folder

Writers:
- MCP_1: MCP to $(DestDataset_MCP)

Creator
    GEOMTYPE = No Geometry
    NUM = 1
    CREATED -> ParameterFetcher
FeatureReader
    ATTRIBUTES = Data,"Electricity,ElectricityUnit,NaturalGas,NaturalGasUnit,""Street Address"",Year,""Property Name"",""Property Type"",""Postal Code"""
    ATTR_ACCUM_MODE = Only Use Result
    COMBINE_GEOM = Use Result
    DATASET = $(FME_MF_DIR_ENCODED)energy-consumption-full.sqlite
    FEATURETYPES = Data
    FORMAT = SQLITE3
    INITIATOR_FIRST_OUTPUT = default
    INPUT_PORT_INITIATOR_CONNECTED = CONNECTED
    MAX_FEATURES = @Value(_LIMIT)
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    SQLITE3_CREATE_FEATURE_TABLES_FROM_DATA = No
    SQLITE3_QUERY_FEATURE_TYPES_FOR_MERGE_FILTERS = Yes
    SQLITE3_SUPPORT_INTERNATIONALIZATION = YES
    WHERE = @Value(WHERE_Query)
    Data -> FeatureJoiner [RIGHT]
    INITIATOR -> JSONTemplater [ROOT]
JSONTemplater
    ENERGY_QUERY_EXPR:
      {
          "Property Name": fme:get-attribute("Property Name"),
          "Property Type": fme:get-attribute("Property Type"),
          "Street Address": fme:get-attribute("Street Address"),
          "Year": fme:get-attribute("Year"),
          "Electricity": fme:get-attribute("Electricity"),
          "Electricity Unit": fme:get-attribute("ElectricityUnit"),
          "Natural Gas": fme:get-attribute("NaturalGas"),
          "Natural Gas Unit": fme:get-attribute("NaturalGasUnit"),
          "X": fme:get-attribute("X"),
          "Y": fme:get-attribute("Y")
               }
    QUERY_VALIDATE = YES
    RESULT_ATTRIBUTE = json_content
    ROOT_QUERY_EXPR:
      [
      fme:process-features("ENERGY")
      ]
    VISIBLE_QUERY_VALIDATE = Yes
    -> Structured Content (writer MCP_1)
Structured Content (writer MCP_1)
    attributes: json_content json

Bookmark: Get parameters and clean them up
ParameterFetcher
    ATTR_LIST = _LIMIT $(LIMIT) _POSTAL_CODE $(POSTAL_CODE) _YEAR $(YEAR)
    -> NullAttributeMapper
NullAttributeMapper
    ATTRCHOICE_ACTION = ALL
    NULL_TREATMENT_LU = DELETEATTR
    SOURCE_ATTR_VAL_LU = EMPTY
    ATTRCHOICE = All Attributes
    NULL_TREATMENT = Missing
    SOURCE_ATTR_VAL = Empty
    -> StringCaseChanger
StringCaseChanger
    ATTRCHOICE = SELECTED
    ATTRLIST = _POSTAL_CODE
    CHANGE_TYPE = upper
    -> AttributeCreator

Bookmark: Create WHERE Clause from parameters
AttributeCreator
    ATTR_TABLE:
      SET_TO _YEAR_REQUEST (varchar(200)) = FME_CONDITIONAL:DEFAULT_VALUE'1 = 1'BOOL_OP;OR;COMPOSITE_TEST;1;TEST _YEAR ATTRIBUTE_HAS_A_VALUE _FME_BLANK_STRING_'"Year" = @Value(_YEAR)'FME_NUM_CONDITIONS2___
      SET_TO _POSTAL_CODE_REQUEST (varchar(200)) = FME_CONDITIONAL:DEFAULT_VALUE'1 = 1'BOOL_OP;AND;COMPOSITE_TEST;1 AND 2 AND 3;TEST _POSTAL_CODE ATTRIBUTE_HAS_A_VALUE _FME_BLANK_STRING_;TEST @StringLength(@Value(_POSTAL_CODE)) = 3;CASE_SENSITIVE_TEST @Value(_POSTAL_CODE) CONTAINS_REGEX ^[A-Z]\d[A-Z]$'"Postal Code" LIKE '@Value(_POSTAL_CODE)%''BOOL_OP;AND;COMPOSITE_TEST;1 AND 2 AND 3;TEST _POSTAL_CODE ATTRIBUTE_HAS_A_VALUE _FME_BLANK_STRING_;CASE_SENSITIVE_TEST @Value(_POSTAL_CODE) CONTAINS_REGEX ^[A-Z]\d[A-Z] \d[A-Z]\d$;TEST @StringLength(@Value(_POSTAL_CODE)) = 7'"Postal Code" = '@Value(_POSTAL_CODE)''FME_NUM_CONDITIONS3___
    INPUT_PORT_CONNECTED = CONNECTED
    -> AttributeCreator_2
AttributeCreator_2
    ATTR_TABLE = SET_TO WHERE_Query (varchar(200)) = @Value(_POSTAL_CODE_REQUEST) AND @Value(_YEAR_REQUEST)
    INPUT_PORT_CONNECTED = CONNECTED
    -> FeatureReader [INITIATOR]

Bookmark: Read addresses GEOJSON
Creator_2
    GEOMTYPE = No Geometry
    NUM = 1
    CREATED -> FeatureReader_2 [INITIATOR]
FeatureReader_2
    ATTRIBUTES = PublicBuildings,"ADDRESS_FULL,CLASS_FAMILY,CLASS_FAMILY_DESC,ADDRESS_CLASS,ADDRESS_CLASS_DESC,PLACE_NAME,OBJECTID"
    ATTR_ACCUM_MODE = Only Use Result
    CLIP_TO_ENVELOPE = NO
    COMBINE_GEOM = Use Result
    DATASET = $(FME_MF_DIR_ENCODED)public-buildings.geojson
    FEATURETYPES = PublicBuildings
    FORMAT = GEOJSON
    GEOJSON_FLATTEN_MODE = ALL_LEVELS
    GEOJSON_USE_BASENAME_AS_DEFAULT_FEATURE_TYPE = Yes
    GEOJSON_USE_SEARCH_ENVELOPE = NO
    GEOMETRY_TYPES = PublicBuildings,""",fme_point"""
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    PublicBuildings -> FeatureJoiner [LEFT]

Bookmark: Join addresses and query results, then extract the coordinates
FeatureJoiner
    ATTR_CONFLICT_RES = USE_LEFT
    GEOMETRY_HANDLING = USE_LEFT
    JOIN_KEYS = ADDRESS_FULL Street Address AUTO
    JOIN_MODE = Inner
    JOINED -> AttributeKeeper
    UNJOINED_RIGHT -> JSONTemplater [ENERGY]
AttributeKeeper
    CREATE_BULK_MODE_FEATURES = NO
    KEEP_ATTRS = Electricity,ElectricityUnit,NaturalGas,NaturalGasUnit,Postal Code,Property Name,Property Type,Street Address,Year
    -> CoordinateExtractor
CoordinateExtractor
    IND = 0
    RECURSIVE = No
    X_ATTR = X
    Y_ATTR = Y
    MODE = Specify Coordinate
    -> JSONTemplater [ENERGY]
